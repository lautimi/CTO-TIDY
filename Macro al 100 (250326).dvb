Attribute VB_Name = "ASIGNAR_NUM_HP"
Sub SeleccionarBloquesPorCapa()
    Dim atts As Variant
    Dim hp_eje As String
    Dim ok As Boolean
    
    Dim doc As Object
    Set doc = ThisDrawing
    
    ' Define las capas de interés
    Dim capa1 As String
    Dim capa2 As String
    capa1 = "CAJA ACCESO b"
    capa2 = "CAJA ACCESO b-PR"

    ' Itera a través de todos los bloques en el dibujo
    Dim blk As Object
    For Each blk In doc.ModelSpace
        ' Verifica si el bloque pertenece a una de las capas de interés
        If (blk.Layer = capa1 Or blk.Layer = capa2) Then
            atts = blk.GetAttributes
            If atts(0).TextString <> "" Then
                hp_eje = atts(0).TextString
                If IsNumeric(hp_eje) Then
                ok = funciones.asignarValorDato(blk, "CAJA_ACCESO", "HP_EJE", hp_eje)
                atts(0).TextString = ""
                End If
            End If
        End If
    Next blk
    
End Sub

Attribute VB_Name = "INSERTAR_CTOS"
#If VBA7 Then
    Private Declare PtrSafe Function GetAsyncKeyState Lib "user32" _
            (ByVal vKey As Long) As Integer
#Else
    Private Declare Function GetAsyncKeyState Lib "user32" _
            (ByVal vKey As Long) As Integer
#End If

Private Const VK_SPACE = &H20
Sub insertarCtos()
    Dim cont_hp As AcadBlockReference
    Dim cto As AcadBlockReference
    Dim atts As Variant
    Dim sdu As Integer
    Dim cadi As Integer
    Dim cacf As Integer
    Dim hp_eje As Integer
    Dim coor As Variant
    Dim aux_point As Variant
    Dim angle As Double
    'On Error Resume Next
    
    
    Do Until GetAsyncKeyState(27)
    
    ThisDrawing.Utility.GetEntity cont_hp, inspt, "Seleccione contador"

    atts = cont_hp.GetAttributes
    sdu = CInt(atts(1).TextString)
    coor = cont_hp.InsertionPoint
    ThisDrawing.Layers("CONTEO HP").Lock = True
    
    If sdu = 0 Then
        cadi = 0
        cacf = 0
    ElseIf sdu <= 2 Then
        cadi = 1
        cacf = 0
    ElseIf sdu <= 8 Then
        cadi = 1
        cacf = 0
    ElseIf sdu <= 16 Then
        cadi = 1
        cacf = 1
    ElseIf sdu <= 20 Then
        cadi = 1
        cacf = 2
    ElseIf sdu <= 24 Then
        cadi = 2
        cacf = 1
    ElseIf sdu <= 32 Then
        cadi = 2
        cacf = 2
    ElseIf sdu <= 40 Then
        cadi = 2
        cacf = 3
    ElseIf sdu <= 48 Then
        cadi = 3
        cacf = 3
    ElseIf sdu <= 56 Then
        cadi = 3
        cacf = 4
    ElseIf sdu <= 64 Then
        cadi = 4
        cacf = 4
    ElseIf sdu <= 72 Then
        cadi = 4
        cacf = 5
    ElseIf sdu <= 80 Then
        cadi = 5
        cacf = 5
    ElseIf sdu <= 88 Then
        cadi = 5
        cacf = 6
    ElseIf sdu <= 96 Then
        cadi = 6
        cacf = 6
    End If
    
    Dim total As Integer
    Dim contador As Integer
    
    contador = 1
    total = cadi + cacf
    
    aux_point = coor
    aux_point(0) = aux_point(0) - 1
    aux_point(1) = aux_point(1) - 1
    ThisDrawing.ActiveLayer = ThisDrawing.Layers("CAJA ACCESO b")
    
    Dim hps_extra() As Integer
    If cadi > 0 Then
        ReDim hps_extra(0 To cadi - 1)
        For i = 0 To cadi - 1
            hps_extra(i) = 0
        Next i
        For i = 0 To (sdu Mod cadi) - 1
            hps_extra(i) = 1
        Next i
        For i = 0 To cadi - 1
        If i = 0 Then
            aux_point(0) = aux_point(0) - Sin(cont_hp.Rotation) * 5.3
            aux_point(1) = aux_point(1) - Cos(cont_hp.Rotation) * 5.3
        
        Else:
            aux_point(0) = aux_point(0) - Cos(cont_hp.Rotation) * 5.3
            aux_point(1) = aux_point(1) - Sin(cont_hp.Rotation) * 5.3
        
        End If
        
            Set cto = ThisDrawing.ModelSpace.InsertBlock(aux_point, "CAJA_ACCESO_b", 1, 1, 1, cont_hp.Rotation)
            atts = cto.GetAttributes
            hp_eje = hps_extra(i) + Int(sdu / cadi)
            
            atts(0).TextString = hp_eje
            
            atts(1).TextString = "CAb"
            contador = contador + 1
        Next i
    End If
    aux_point = coor
    aux_point(0) = aux_point(0) - 1
    aux_point(1) = aux_point(1) - 1
    ThisDrawing.ActiveLayer = ThisDrawing.Layers("CAJA ACCESO b-PR")
    For i = 0 To cacf - 1
        If i = 0 Then
            aux_point(0) = aux_point(0) + (Cos(cont_hp.Rotation) - Sin(cont_hp.Rotation)) * 5.3
            aux_point(1) = aux_point(1) + (Sin(cont_hp.Rotation) - Cos(cont_hp.Rotation)) * 5.3
        Else:
            aux_point(0) = aux_point(0) + Cos(cont_hp.Rotation) * 5.3
            aux_point(1) = aux_point(1) + Sin(cont_hp.Rotation) * 5.3
        
        End If
        Set cto = ThisDrawing.ModelSpace.InsertBlock(aux_point, "CAJA_CRECIMIENTO", 1, 1, 1, cont_hp.Rotation)
        
        atts = cto.GetAttributes

        atts(0).TextString = ""

        atts(1).TextString = "CAbc"
        contador = contador + 1
        
    Next i
    
    ThisDrawing.Layers("CONTEO HP").Lock = False
    
    Set cont_hp = Nothing
   Loop

    
End Sub

Attribute VB_Name = "NUM_HP"
#If VBA7 Then
    Private Declare PtrSafe Function GetAsyncKeyState Lib "user32" _
            (ByVal vKey As Long) As Integer
#Else
    Private Declare Function GetAsyncKeyState Lib "user32" _
            (ByVal vKey As Long) As Integer
#End If

Private Const VK_SPACE = &H20
Sub contarHp()
   Dim ss As AcadSelectionSet
   Dim sdu As String
   Dim mdu As String
   Dim numPisos As Integer
   Dim numUnidades As Integer
   Dim pisos As Integer
   Dim hps As Integer
   Dim cont_hp As AcadBlockReference
   Dim contador As Variant
   Dim segmento As AcadObject
   Dim segAttr As Variant
    Dim objSS As AcadSelectionSet
    Dim angle As Double
    Dim coor As Variant
    Dim c1(0 To 2) As Double
    Dim c2(0 To 2) As Double
    Dim MyObject As Variant
    
    Do Until GetAsyncKeyState(27)
        On Error Resume Next
        Set objSS = ThisDrawing.SelectionSets.Item("AMODIFIER")
        If Err Then
        Err.Clear
        Else
        objSS.Delete
        End If
        Set objSS = ThisDrawing.SelectionSets.Add("AMODIFIER")
        objSS.SelectOnScreen
            ThisDrawing.Utility.Prompt vbCr & objSS.Count & " entidades seleccionadas" & vbNewLine
        sdu = 0
        mdu = 0
        For Each MyObject In objSS
        If Left(MyObject.Layer, 10) = "PROPIEDAD_" Then
            Dim blkRef As AcadBlockReference
            Set blkRef = MyObject
            hps = funciones.obtenerDato(blkRef, "PROPIEDAD", "CANT_DEPARTAMENTOS") + funciones.obtenerDato(blkRef, "PROPIEDAD", "CANT_LOCALES")
            pisos = funciones.obtenerDato(blkRef, "PROPIEDAD", "CANT_PISOS")
            If pisos >= 3 Or hps >= 7 Then
                mdu = mdu + hps
            Else
                sdu = sdu + hps
            End If
        ElseIf MyObject.Layer = "SEGMENTO" Then
            Set segmento = MyObject
        End If
        Next
        If sdu = 0 And mdu = 0 Then GoTo ErrorHp
        If segmento.ObjectName = Null Then GoTo ErrorSegmento
        
        If segmento.ObjectName = "AcDbPolyline" Then
            segAttr = FindCentriod(segmento)
            coor = segmento.Coordinatesf
            c1(0) = coor(0): c1(1) = coor(1): c1(2) = 0
            c2(0) = coor(UBound(coor) - 1): c2(1) = coor(UBound(coor)): c2(2) = 0
            angle = getAngle(c1, c2)
        ElseIf segmento.ObjectName = "AcDbLine" Then
            segAttr = FindCentroidForLine(segmento)
            angle = getAngle(segmento.startPoint, segmento.endPoint)
        End If
        
        GoTo Contar
    
ErrorSegmento:
    angle = 0
    segAttr = ThisDrawing.Utility.GetPoint(, vbCr & "Seleccionar punto a colocar")
Contar:
    ThisDrawing.ActiveLayer = ThisDrawing.Layers("CONTEO HP")
    Set cont_hp = ThisDrawing.ModelSpace.InsertBlock(segAttr, "CONT_HP", 1, 1, 1, angle)
    contador = cont_hp.GetAttributes()
    contador(0).TextString = mdu
    contador(1).TextString = sdu
    
    
    Loop
    
    Exit Sub
    
ErrorHp:
    MsgBox "No hay puntos de vivienda seleccionados. Fin del programa."
    Exit Sub
    
End Sub

Function FindCentriod(oEntity As AcadEntity) As Variant
    Dim dblCentroid(0 To 2) As Double
    Dim varPts As Variant
    Dim intTotPts As Variant
    Dim dblX As Double, dblY As Double
    Dim n As Integer

    With oEntity
        If .ObjectName = "AcDbPolyline" Then
            varPts = .Coordinates

            intTotPts = (UBound(varPts) + 1) / 2

            If intTotPts > 0 Then
                For n = 0 To (intTotPts * 2 - 1) Step 2
                    dblX = dblX + varPts(n)
                    dblY = dblY + varPts(n + 1)
                Next n

                dblCentroid(0) = dblX / intTotPts
                dblCentroid(1) = dblY / intTotPts
            End If
        Else
            Err.Raise vbObjectError + 1, "FindCentroid", "Segmento incorrecto"
        End If
    End With

    FindCentriod = dblCentroid
End Function
Function FindCentroidForLine(oEntity As AcadEntity) As Variant
    Dim dblCentroid(0 To 2) As Double
    Dim dblX1 As Variant, dblY1 As Variant
    Dim dblX2 As Double, dblY2 As Double
    Set oEntity2 = oEntity
    With oEntity2
        If .ObjectName = "AcDbLine" Then
            dblX1 = .startPoint
            dblY1 = .endPoint

            dblCentroid(0) = (dblX1(0) + dblY1(0)) / 2
            dblCentroid(1) = (dblY1(1) + dblX1(1)) / 2
        Else
            Err.Raise vbObjectError + 1, "FindCentroidForLine", "Segmento incorrecto"
        End If
    End With

    FindCentroidForLine = dblCentroid
End Function
Public Function getAngle(startPnt As Variant, endPnt As Variant) As Double
    Dim grade As Double
    Dim retAngle As Double
    Dim pi As Double
    pi = 3.1416
    getAngle = ThisDrawing.Utility.AngleFromXAxis(startPnt, endPnt) - pi
    End Function

Attribute VB_Name = "funciones"
Function obtenerDato(objeto As Variant, tabla As String, campo As String)
    Dim i As Integer
    
    Dim iCampo As Integer
    
    Dim amap As AcadMap

    Dim ODrcs As ODRecords
    
    Dim boolVal As Boolean
    
    Dim retVal As Variant
    
    Dim prj As Project
    
    Dim defs As ODFieldDefs
    
    
    Set amap = ThisDrawing.Application.GetInterfaceObject("AutoCADMap.Application")
    
    Set prj = amap.Projects(ThisDrawing)
    
    Set ODrcs = prj.ODTables.GetODRecords
    
    i = 0
    
    For Each table In prj.ODTables
        If table.Name = tabla Then
            Set defs = table.ODFieldDefs
            For i = 0 To table.ODFieldDefs.Count - 1
            
                If defs.Item(i).Name = campo Then
                    iCampo = i
                    Exit For
                End If
            Next i
        End If
    Next
    boolVal = ODrcs.Init(objeto, False, False)
    Do While ODrcs.IsDone = False
    
    retVal = ODrcs.Record.Item(iCampo).Value
    
    ODrcs.Next
    Loop
    
    obtenerDato = retVal
    
End Function
Function asignarValorDato(objeto As Variant, tabla As String, campo As String, valor As String)
    Dim i As Integer
    
    Dim iCampo As Integer
    
    Dim amap As AcadMap

    Dim ODrcs As ODRecords
    
    Dim boolVal As Boolean
    
    Dim retVal As Variant
    
    Dim prj As Project
    
    Dim defs As ODFieldDefs
    
    Set amap = ThisDrawing.Application.GetInterfaceObject("AutoCADMap.Application")
    
    Set prj = amap.Projects(ThisDrawing)
    
    Set ODrcs = prj.ODTables.GetODRecords
    For Each table In prj.ODTables
        If table.Name = tabla Then
            Set defs = table.ODFieldDefs
            For i = 0 To table.ODFieldDefs.Count - 1
            
                If defs.Item(i).Name = campo Then
                    iCampo = i
                    Exit For
                End If
            Next i
        End If
    Next
    
    boolVal = ODrcs.Init(objeto, True, False)
    Do While ODrcs.IsDone = False
        Set newRecord = ODrcs.Record
    
        newRecord.Item(iCampo).Value = valor
            
        retVal = ODrcs.Update(newRecord)

        ODrcs.Next
    Loop
    
End Function
Function asignarBloqueATabla(bloque As AcadObject, nombreTabla As String)
    Dim ODrcs As ODRecords
    Dim OTables As ODTables
    Dim OTable As ODTable
    Dim boolVal As Boolean
    Dim oRecord As ODRecord
    Dim returnObj As AcadObject
    Dim basePnt As Variant
    Dim strValue As String
    Dim MTextObj As AcadMText
    Dim oID As Long
    
    oID = CLng(bloque.ObjectID)
    Set amap = ThisDrawing.Application.GetInterfaceObject("AutoCADMap.Application")
    Set OTables = amap.Projects.Item(ThisDrawing).ODTables
    For Each tabla In OTables
        If tabla.Name = nombreTabla Then
            
            Set OTable = tabla
        End If
    Next
    
    Set ODrcs = OTable.GetODRecords
    Set oRecord = OTable.CreateRecord
    oRecord.Item(1).Value = "0"
    bRetVal = oRecord.AttachTo(oID)
End Function
